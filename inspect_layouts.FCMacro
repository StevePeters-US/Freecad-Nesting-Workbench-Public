"""
inspect_layouts.FCMacro
Dumps the full object tree of Layout_000 and Layout_001 (old vs new) side-by-side.
Run via: Macro > Macros... > Execute in FreeCAD
"""
import FreeCAD


def dump_tree(obj, indent=0):
    prefix = "  " * indent
    type_id = getattr(obj, "TypeId", "?")
    label = getattr(obj, "Label", "?")
    name = getattr(obj, "Name", "?")
    in_list = [p.Label for p in getattr(obj, "InList", [])]
    line = f"{prefix}[{name}] Label={label!r} TypeId={type_id} InList={in_list}"
    FreeCAD.Console.PrintMessage(line + "\n")

    if hasattr(obj, "Group"):
        for child in obj.Group:
            dump_tree(child, indent + 1)


doc = FreeCAD.ActiveDocument
if not doc:
    FreeCAD.Console.PrintError("No active document.\n")
else:
    targets = []
    for obj in doc.Objects:
        if obj.isDerivedFrom("App::DocumentObjectGroup") and obj.Label.startswith("Layout_"):
            targets.append(obj)

    targets.sort(key=lambda o: o.Label)

    if not targets:
        FreeCAD.Console.PrintMessage("No Layout_ groups found in document.\n")

    for layout in targets[:2]:  # Show at most 2 layouts
        FreeCAD.Console.PrintMessage(f"\n{'='*60}\n")
        FreeCAD.Console.PrintMessage(f"LAYOUT: {layout.Label} ({layout.Name})\n")
        FreeCAD.Console.PrintMessage(f"{'='*60}\n")
        dump_tree(layout)

    # Also list any orphaned nested_* or Shapes_* objects not inside a Layout
    FreeCAD.Console.PrintMessage(f"\n{'='*60}\n")
    FreeCAD.Console.PrintMessage("ORPHANED objects (nested_* / Shapes_* / Sheet_* not under a Layout):\n")
    FreeCAD.Console.PrintMessage(f"{'='*60}\n")
    layout_names = {o.Name for o in targets}

    def is_under_layout(obj):
        visited = set()
        stack = list(getattr(obj, "InList", []))
        while stack:
            p = stack.pop()
            if p.Name in visited:
                continue
            visited.add(p.Name)
            if p.Name in layout_names:
                return True
            stack.extend(getattr(p, "InList", []))
        return False

    for obj in doc.Objects:
        label = getattr(obj, "Label", "")
        if any(label.startswith(pfx) for pfx in ("nested_", "Shapes_", "Sheet_", "part_", "boundary_")):
            if not is_under_layout(obj):
                FreeCAD.Console.PrintMessage(
                    f"  ORPHAN [{obj.Name}] Label={label!r} TypeId={obj.TypeId} "
                    f"InList={[p.Label for p in obj.InList]}\n"
                )
